module ietf-te-wson-types {
  namespace "urn:ietf:params:xml:ns:yang:ietf-te-wson-types";
  prefix "te-wson-types";

  organization
    "IETF CCAMP Working Group";
  contact
    "WG Web: <http://tools.ietf.org/wg/ccamp/>
     WG List: <mailto:ccamp@ietf.org>

    Editor: Aihua Guo
      <mailto:aihuaguo@huawei.com>

    Editor: Young Lee
      <mailto:leeyoung@huawei.com>";

  description
    "This module defines WSON types.";

  revision "2018-08-15" {
    description
      "Revision 3";
    reference "TBD";
  }

  typedef operational-mode {
    type string;
    description
      "Vendor-specific mode that guarantees interoperability.
       It must be an string with the following format:
       B-DScW-ytz(v) where all these attributes are conformant
       to the ITU-T recomendation";
    reference "ITU-T G.698.2 (11/2009) Section 5.3";
  }

  identity wson-node-type {
    description
      "WSON node type.";
    reference
      "RFC6163";
  }

  identity wson-node-foadm {
    base wson-node-type;
    description
      "Fixed OADM node.";
  }

  identity wson-node-roadm {
    base wson-node-type;
    description
      "ROADM or OXC node.";
  }

  identity wson-node-ila {
    base wson-node-type;
    description
      "ILA (In-Line Amplifier) node.";
  }

  /* TODO - remove the definition once WSON topology model 
     is updated */
  typedef wavelength-range-type {
    type string {
      pattern "([1-9][0-9]{0,3}(-[1-9][0-9]{0,3})?" +
              "(,[1-9][0-9]{0,3}(-[1-9][0-9]{0,3})?)*)";
    }
    description
      "A list of WDM channel numbers (starting at 1)
      in ascending order. For example: 1,12-20,40,50-80";
  }

  identity wavelength-assignment {
    description 
    "Wavelength selection base";
  }

  identity unspecified-wavelength-assignment {
    base wavelength-assignment;
    description 
      "No method specified";
  }

  identity first-fit-wavelength-asignment {
    base wavelength-assignment;
    description 
      "All the available wavelengths are numbered,
       and this WA method chooses the available wavelength
       with the lowest index.";
  }

  identity random-wavelength-asignment {
    base wavelength-assignment;
    description 
      "This WA method chooses an available
       wavelength randomly.";
  }

  identity least-loaded-wavelength-asignment {
    base wavelength-assignment;
    description 
      "This WA method selects the wavelength that
       has the largest residual capacity on the most loaded
       link along the route (in muli-fiber networks).";
  }

  identity wson-grid-type {
    description
      "WSON grid type.";
  }

  identity wson-grid-dwdm {
    base wson-grid-type;
    description
      "DWDM grid.";
  }
  
  identity wson-grid-cwdm {
    base wson-grid-type;
    description
      "CWDM grid.";
  }
  
  identity wson-bandwidth-type {
    description
      "Bandwidth type carried by a single wavelength channel.";
  }

  identity wson-bw-otu1 {
    base wson-bandwidth-type;
    description
      "OTU1 (2.66G)";
  }

  identity wson-bw-otu1e {
    base wson-bandwidth-type;
    description
      "OTU1e(11.04G)";
  }

  identity wson-bw-otu1f {
    base wson-bandwidth-type;
    description
      "OTU1f(11.27G)";
  }

  identity wson-bw-otu2 {
    base wson-bandwidth-type;
    description
      "OTU2 (10.70G)";
  }

  identity wson-bw-otu2e {
    base wson-bandwidth-type;
    description
      "OTU2e (11.09G)";
  }

  identity wson-bw-otu2f {
    base wson-bandwidth-type;
    description
      "OTU2f (11.31G)";
  }

  identity wson-bw-otu3 {
    base wson-bandwidth-type;
    description
      "OTU3 (43.01G)";
  }

  identity wson-bw-otu3e1 {
    base wson-bandwidth-type;
    description
      "OTU3e1 (44.57G)";
  }

  identity wson-bw-otu3e2 {
    base wson-bandwidth-type;
    description
      "OTU3e2 (44.58G)";
  }

  identity wson-bw-otu4 {
    base wson-bandwidth-type;
    description
      "OTU4 (111.80G)";
  }

  identity wson-bw-otucn {
    base wson-bandwidth-type;
    description
      "OTUCn (beyond 100G)";
  }
  
  identity dwdm-ch-spc-type {
    description 
      "DWDM channel spacing type.";
  }

  identity dwdm-100ghz {
    base dwdm-ch-spc-type;
    description 
      "100GHz channel spacing";
  }

  identity dwdm-50ghz {
    base dwdm-ch-spc-type;
    description 
      "50GHz channel spacing";
  }

  identity dwdm-25ghz {
    base dwdm-ch-spc-type;
    description 
      "25GHz channel spacing";
  }

  identity dwdm-12p5ghz {
    base dwdm-ch-spc-type;
    description 
      "12.5GHz channel spacing";
  }

  identity cwdm-ch-spc-type {
    description 
      "CWDM channel spacing type.";
  }

  identity cwdm-20nm {
    base cwdm-ch-spc-type;
    description 
      "20nm channel spacing";
  }

  identity fec-type {
    description
      "FEC type.";
  }

  identity g-fec {
    base fec-type;
    description
      "G-FEC.";
  }
  identity e-fec {
    base fec-type;
    description
      "E-FEC.";
  }
  identity no-fec {
    base fec-type;
    description
      "No FEC.";
  }
  
  identity term-type {
    description
      "Termination type.";
  }

  identity term-phys {
    base term-type;
    description
      "PHYS.";
  }
  identity term-otu {
    base term-type;
    description
      "OTU.";
  }
  identity term-odu {
    base term-type;
    description
      "ODU.";
  }
  identity term-opu {
    base term-type;
    description
      "OPU.";
  }
  identity term-section {
    base term-type;
    description
      "Section.";
  }
  
  /* Groupings. */
  grouping wson-path-bandwidth {
    description "WSON path bandwidth attributes";
    leaf bandwidth-type {
      type identityref {
        base wson-bandwidth-type;
      }
      description "WSON bandwidth type";
    }
  }

  grouping wson-link-bandwidth {
    description "WSON link bandwidth attributes";
    leaf-list supported-bandwidth-list {
      type identityref {
        base wson-bandwidth-type;
      }
      description "WSON bandwidth type";
    }
  }

  grouping wson-label {
    description 
      "Generic label for WSON links and paths";
    choice grid-type {
      description
        "Label for DWDM or CWDM grid";
      case dwdm {
        leaf channel-freq {
          type decimal64 {
            fraction-digits 5;
          }
          units THz;
          description
            "The DWDM frequency in THz, e.g. 193.12500";
          reference
            "RFC6205";
        }
      }
      case cwdm {
        leaf channel-wavelength {
          type uint32;
          units nm;
          description
            "The CWDM wavelength in nanometer, e.g. 1511";
          reference
            "RFC6205";
        }
      }
    }
  }

  grouping wson-link-label {
    description 
      "Link label information for WSON links, for label-start/end";
    uses te-wson-types:wson-label;
  }

  grouping wson-path-label {
    description 
      "Path label information for WSON links, for label-hop";
    uses te-wson-types:wson-label;
  }

  grouping wson-label-restriction {
    description
      "WSON label restriction.";

    leaf grid-type {
      type identityref {
        base te-wson-types:wson-grid-type;
      }
      description "Grid type";
    }
    leaf priority {
      type uint8;
      description "priority.";
    }
  }

  grouping wson-label-step {
    description "Label step information for WSON";
    choice wson-grid-type {
      description
        " WSON grid-type: DWDM, CWDM, etc.";
      case dwdm {
        leaf wson-dwdm {
          type identityref {
            base te-wson-types:dwdm-ch-spc-type;
          }
          description
            "Label-step is the channel-spacing (GHz), e.g., 
             100, 50, 25, or 12.5 GHz for DWDM.";
          reference
            "rfc6205";
        }
      }
      case cwdm {
        leaf wson-cwdm {
          type identityref {
            base te-wson-types:cwdm-ch-spc-type;
          }
          description
            "label-step is the channel-spacing (nm), i.e.,
             20 nm for CWDM, which is the only value defined for CWDM.";
          reference
            "rfc6205.";
        }
      }
    }
  }
}
