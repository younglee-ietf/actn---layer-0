module   ietf-wson-impairment-topology {  
  yang-version 1.1;

  namespace "urn:ietf:params:xml:ns:yang:ietf-wson-impairment-topology";

  prefix "wson-imp";

  import ietf-network {
    prefix "nw";
  }

  import ietf-network-topology {
    prefix "nt";
  }

  import ietf-te-topology {
    prefix "tet";
  }
  
  import ietf-wson-topology {
    prefix "wson";
  }
  
  import ietf-te-wson-types {
    prefix "te-wson-types";
  }

  organization
    "IETF CCAMP Working Group";

  contact
    "Editor:   Young Lee  <leeyoung@huawei.com>";

  description
	"This module contains a collection of YANG definitions for
	Impairment-aware RWA WSON.

	Copyright (c) 2018 IETF Trust and the persons identified as
	authors of the code.  All rights reserved.

	Redistribution and use in source and binary forms, with or
	without modification, is permitted pursuant to, and subject
	to the license terms contained in, the Simplified BSD
	License set forth in Section 4.c of the IETF Trust's Legal
	Provisions Relating to IETF Documents
	(http://trustee.ietf.org/license-info).";

  revision 2018-08-23 {
	description
	   "version 0.";
	   reference
		  "RFC XXX: A Yang Data Model for Impairment-aware WSON Optical Networks ";
  }

  typedef modulation {
    type enumeration {
	  enum QPSK {
		  description 
		  "QPSK (Quadrature Phase Shift Keying) modulation";
	  }
	  enum DP_QPSK {
		  description "DP-QPSK (Dual Polarization Quadrature
		  Phase Shift Keying) modulation"; 
	  }
	  enum QAM16 {
		  description "QAM16 (Quadrature Amplitude Modulation
		  - 4 bits per symbol) modulation";
	  }
	  enum DP_QAM16 {
		  description "DP-QAM16 (Dual Polarization 
		  Quadrature Amplitude Modulation - 4 bits per
		  symbol) modulation";
	  }
	  enum DC_DP_QAM16 {
		  description "DC DP-QAM16 (Dual Polarization
		    Quadrature Amplitude Modulation - 4 bits per
		    symbol) modulation";
	  }
    }
    description 
	  "Enumeration that defines the type of wave modulation";
  }

  typedef FEC {
    type enumeration {
	  enum reed-solomon {
		  description "Reed-Solomon error correction";
	  }
	  enum hamming-code{
		  description "Hamming Code error correction";
	  }
	  enum golay{
		  description "Golay error correction";
	  }
    }
    description "Enumeration that defines the type of 
      Forward Error Correction";
  }
  
  grouping wson-label {
    description 
      "Generic label for WSON links and paths";
    choice grid-type {
      description
        "Label for DWDM or CWDM grid";
      case dwdm {
        leaf channel-freq {
          type decimal64 {
            fraction-digits 5;
          }
          units THz;
		  config false;
          description
            "The DWDM frequency in THz, e.g. 193.12500";
          reference
            "RFC6205";
        }
      }
      case cwdm {
        leaf channel-wavelength {
          type uint32;
          units nm;
		  config false;
          description
            "The CWDM wavelength in nanometer, e.g. 1511";
          reference
            "RFC6205";
        }
      }
    }
  }

	
  grouping transponder-attributes {
	description "Configuration of an optical transponder";
	leaf-list available-modulation {
		type modulation;
		config false;
		description 
			"List determining all the available modulations";
	}
	leaf modulation-enabled {
		type boolean;
		config false; 
		description 
			"Determines whether the modulation is enabled or not";
	}
	leaf modulation-type {
		type modulation;
		config false;
		description 
			"Modulation type of the transponder";
	}
	leaf-list available-FEC {
		type FEC;
		config false;
		description "List determining all the available FEC";
	}
	leaf FEC-enabled {
		type boolean;
		config false; 
		description 
			"Determines whether the FEC is enabled or not";
	}
	leaf FEC-type {
		type FEC;
		config false;
		description 
			"FEC type of the transponder";
	}
	leaf FEC-code-rate {
		type decimal64 {
		  fraction-digits 8;
		  range "0..max";
		}
		config false;
		description "FEC-code-rate";
	}
	leaf FEC-threshold {
		type decimal64 {
		  fraction-digits 8;
		  range "0..max";
		}
		config false;
		description "Threshold on the BER, for which FEC is able to correct errors";
	}
  }
	  
  grouping sliceable-transponder-attributes {
	description
		"Configuration of a sliceable transponder.";
	list transponder-list {
		key "carrier-id";
		config false;
		description "List of carriers";
		leaf carrier-id {
			type uint32;
			config false;
			description "Identifier of the carrier";
		}
	}        
  }

  grouping wson-node-attributes {
	description "WSON node attributes";
	container wson-node {
	   description "WSON node attrtibutes.";
	   leaf node-type {
		 type identityref {
			base te-wson-types:wson-node-type;
		 }
		 description "WSON node type.";
	   }
	}
  }

  grouping wson-fiber-data {
	description "WSON link (fiber) attributes with impairment data";
	  leaf power {
		type int32;
		units "dBm";
		config false; 
		description "Input Power Level of the receiver side of the link";
      }
  }
  
  grouping wson-impairement-data {
	description "WSON impairment data per wavelength"; 
	  leaf bit-rate {
	    type decimal64 {
		   fraction-digits 8;
		   range "0..max";
	    }
	    units "Gbit/s";
		config false;
	    description "Gross bit rate";
	  }
	  leaf BER {
	    type decimal64 {
		  fraction-digits 18;
		    range "0..max";
		  }
		  config false;
		  description "BER";
	  }
	  leaf pmd {
	    type decimal64 {
		  fraction-digits 8;
		  range "0..max";
	    }
	    units "ps/(km)^0.5";
	    config false; 
		  description "Polarization Mode Dispersion";
	  }
	  leaf cd {
	    type decimal64 {
		  fraction-digits 5;
	    }
	    units "ps/nm/km";
	    config false; 
	    description "Cromatic Dispersion";
	  }
	  leaf osnr {
	    type decimal64 {
		  fraction-digits 5;
	    }
	    units "dB";
	    config false; 
	    description "osnr"; 
	  }
	  leaf q-factor {
	    type decimal64 {
		  fraction-digits 5;
	    }
	    units "dB";
	    config false; 
	    description "q-factor"; 
	  }
  }

  /*
  grouping wson-ttp-attributes {
	 description 
	   "WSON tunnel termination point (e.g.tranponder) attributes";
		leaf-list available-operational-mode {
		  type te-wson-types:operational-mode;
		  description "List of all vendor-specific supported
		  mode identifiers";
		}

		leaf operational-mode {
		  type te-wson-types:operational-mode;
		  description "Vendor-specific mode identifier";
		}
  }
  */ 

/* Data nodes */

  augment "/nw:networks/nw:network/nw:network-types"
	 + "/tet:te-topology" {
	 description "wson-impairment topology augmented";
	 container wson-impairment-topology {
	   presence "indicates an impairment-aware topology of wson";
	   description
		 "Container to identify impairment-aware wson topology type";
	 }
  }

  augment "/nw:networks/nw:network/nt:link/tet:te"
	 + "/tet:te-link-attributes"   {
	 when "/nw:networks/nw:network/nw:network-types"
		+"/tet:te-topology/wson-imp:wson-impairment-topology" {
		description
		  "This augment is only valid for WSON Impairment.";
	 }
	 description "WSON Link augmentation for impairment data.";
	 uses wson-fiber-data;
  }
  
    /* Augment label hop of underlay primary path of TE link */
  augment "/nw:networks/nw:network/nt:link/tet:te/"
        + "tet:te-link-attributes/"
        + "tet:underlay/tet:primary-path/tet:path-element/tet:type/"
        + "tet:label/tet:label-hop/tet:te-label/tet:technology" {
    when "../../../../../../../../"
       + "nw:network-types/tet:te-topology/"
       + "wson:wson-topology" {
      description "Augment WSON TE label";
    }
    description "WSON label.";
    case wson {
      uses wson-label;
	  uses wson-impairement-data;
    }
  }

  /* Augment label hop of underlay backup path of TE link */
  augment "/nw:networks/nw:network/nt:link/tet:te/"
        + "tet:te-link-attributes/"
        + "tet:underlay/tet:backup-path/tet:path-element/tet:type/"
        + "tet:label/tet:label-hop/tet:te-label/tet:technology" {
    when "../../../../../../../../"
       + "nw:network-types/tet:te-topology/"
       + "wson:wson-topology" {
      description "Augment WSON TE label";
    }
    description "WSON label.";
    case wson-imp {
      uses wson-label;
	  uses wson-impairement-data;
    }
  }
    /* Augment label hop of underlay primary path of TE link template */
  augment "/nw:networks/tet:te/tet:templates/"
        + "tet:link-template/tet:te-link-attributes/"
        + "tet:underlay/tet:primary-path/tet:path-element/tet:type/"
        + "tet:label/tet:label-hop/tet:te-label/tet:technology" {
/*
    when "../../../../../../../../../"
       + "nw:network-types/tet:te-topology/"
       + "wson:wson-topology" {
          description "Augment WSON TE label";
    }
*/
    description "WSON label.";
    case wson-imp {
      uses wson-label;
	  uses wson-impairement-data;
    }
  }

  /* Augment label hop of underlay backup path of TE link template */
  augment "/nw:networks/tet:te/tet:templates/"
        + "tet:link-template/tet:te-link-attributes/"
        + "tet:underlay/tet:backup-path/tet:path-element/tet:type/"
        + "tet:label/tet:label-hop/tet:te-label/tet:technology" {
/*
    when "../../../../../../../../../"
       + "nw:network-types/tet:te-topology/"
       + "wson:wson-topology" {
      description "Augment WSON TE label";
    }
*/
    description "WSON label.";
    case wson-imp {
      uses wson-label;
	  uses wson-impairement-data;
    }
  }
  
	
  

	 
  augment "/nw:networks/nw:network/nw:node/tet:te"
	 + "/tet:te-node-attributes" {
	 when "/nw:networks/nw:network/nw:network-types"
		+"/tet:te-topology/wson:wson-topology" {
		description
		  "This augment is only valid for WSON.";
	 }
	 description "WSON Node augmentation.";
	 uses wson-node-attributes;
  }


  augment "/nw:networks/nw:network/nw:node/tet:te"
	 + "/tet:tunnel-termination-point" {
	 when "/nw:networks/nw:network/nw:network-types"
		+"/tet:te-topology/wson-imp:wson-impairment-topology" {
		description
		  "This augment is only valid for Impairment WSON with non-sliceable 
		  transponder model";
	 }
	 description 
	   "WSON tunnel termination point
	   augmentation for non-sliceabletransponder model.";

	/* uses wson-ttp-attributes; */
	 uses transponder-attributes; 
  }

  augment "/nw:networks/nw:network/nw:node/tet:te"
	 + "/tet:tunnel-termination-point" {
	 when "/nw:networks/nw:network/nw:network-types"
		+"/tet:te-topology/wson-imp:wson-impairment-topology" {
		description
		  "This augment is only valid for Impairment WSON with sliceable 
		  transponder model";
	 }
	 description 
	   "WSON tunnel termination point augmentation for sliceabletransponder model.";
	 uses sliceable-transponder-attributes; 
  }
}
