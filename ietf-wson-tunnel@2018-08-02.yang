module ietf-wson-tunnel {
    //TODO: FIXME
    //yang-version 1.1;

    namespace "urn:ietf:params:xml:ns:yang:ietf-wson-tunnel";
    prefix "wson-tunnel";

    import ietf-te { prefix "te"; }
    import ietf-otn-types{ prefix "otn-types"; }
    import ietf-te-wson-types { prefix "wson-types"; }
    import ietf-te-path-computation { prefix "tepc"; }

    organization
        "IETF CCAMP Working Group";

    contact
        "WG Web:   <http://tools.ietf.org/wg/ccamp/>
         WG List:  <mailto:ccamp@ietf.org>

         WG Chair: Daniele Ceccarelli
                    <mailto:daniele.ceccarelli@ericsson.com>

         WG Chair: Fatai Zhang
                    <mailto:zhangfatai@huawei.com>

         Editor: Young Lee <leeyoung@huawei.com>
         Editor: Dhruv Dhody <dhruv.ietf@gmail.com>
         Editor: Ricard Vilalta <ricard.vilalta@cttc.es>";
         description
             "This module defines a model for WSON Tunnel Services.";


    revision "2018-08-02" {
        description
             "Updates to version 4";
        reference "version 4";
    }

    grouping wson-tunnel-endpoint {
        description "Parameters for OTN tunnel.";

        leaf src-client-signal {
                type identityref {
                        base otn-types:client-signal;
                }
                description
                        "Client signal at the source endpoint of
                        the tunnel.";
        }

        leaf dst-client-signal {
            type identityref {
                    base otn-types:client-signal;
            }
            description
                    "Client signal at the destination endpoint of
                    the tunnel.";
        }
    }
	
	grouping wson-tunnel {
		description "WSON tunnel with resources it occupies"; 
		reference "rfc7581 & rfc7579"; 
		leaf channel-frequency {
			type decimal64 {
				fraction-digits 5;
			}
			units THz;
			description 
				"central channel frequency in the grid. 
				f= 193.1 THz + N x 0.00625 THz, where
				193.1 THz is the anchor frequency for 
				transmission over the C band";
		}
		leaf N {
			type int32;
			description 
				"The corresponding N value in the channel-frequency
                 determination"; 
		}
	}

    grouping wson-path-constraints {
      description
        "Global named path constraints configuration
         grouping for WSON tunnel";
         
      leaf wavelength-assignment {
        type identityref {
          base wson-types:wavelength-assignment;
        }
        description "Wavelength Allocation Method";
      }
    }

    augment "/te:te/te:tunnels/te:tunnel" {
        description
                "Augment with additional parameters required for WSON
                tunnel.";
        uses wson-tunnel-endpoint;
		uses wson-tunnel; 
    }

    augment "/te:te/te:tunnels/te:tunnel/te:state" {
        description
                "Augment with additional parameters required for WSON
                tunnel.";
        uses wson-tunnel-endpoint;
		uses wson-tunnel; 
    }

    augment "/te:te/te:globals/te:named-path-constraints/"
        + "te:named-path-constraint" {
        description
                "Augment with additional constraints WSON
                tunnel.";
        uses wson-path-constraints;
    }

    augment "/te:tunnels-rpc/te:input/te:tunnel-info/"
        + "tepc:request-list" {
        description 
				"Augment with additional constraints WSON
                tunnel.";
		uses wson-tunnel-endpoint;
        uses wson-path-constraints;
    }

    
}
