module ietf-wson-tunnel {
    //TODO: FIXME
    //yang-version 1.1;

    namespace "urn:ietf:params:xml:ns:yang:ietf-wson-tunnel";
    prefix "wson-tunnel";

    import ietf-te { prefix "te"; }
    import ietf-otn-types{ prefix "otn-types"; }
    import ietf-te-wson-types { prefix "wson-types"; }
    import ietf-te-path-computation { prefix "tepc"; }

    organization
        "IETF CCAMP Working Group";

    contact
        "WG Web:   <http://tools.ietf.org/wg/ccamp/>
         WG List:  <mailto:ccamp@ietf.org>

         WG Chair: Daniele Ceccarelli
                    <mailto:daniele.ceccarelli@ericsson.com>

         WG Chair: Fatai Zhang
                    <mailto:zhangfatai@huawei.com>

         Editor: Young Lee <leeyoung@huawei.com>
         Editor: Dhruv Dhody <dhruv.ietf@gmail.com>
         Editor: Ricard Vilalta <ricard.vilalta@cttc.es>";
         description
             "This module defines a model for WSON Tunnel Services.";


    revision "2018-08-13" {
        description
             "Updates to version 4";
        reference "version 4";
    }

    typedef channel-spacing-type {
		
		type enumeration {
			enum 100 {
				description "100GHz Channel Spacing";
			}
			enum 50 {
				description "50GHz Channel Spacing";
			}
			enum 25 {
				description "25GHz Channel Spacing";
			}
			enum 12.5 {
				description "12.5GHz Channel Spacing";
			}
	    }
		description "enmumerated type for DWDM channel-spacing";
	}
	
	grouping wson-tunnel-endpoint {
        description "Parameters for OTN tunnel.";

        leaf src-client-signal {
                type identityref {
                        base otn-types:client-signal;
                }
                description
                        "Client signal at the source endpoint of
                        the tunnel.";
        }

        leaf dst-client-signal {
            type identityref {
                    base otn-types:client-signal;
            }
            description
                    "Client signal at the destination endpoint of
                    the tunnel.";
        }
    }
	
	grouping wson-tunnel-resource {
		description "WSON resource configured for a tunnel"; 
		reference "rfc6205 & rfc7581 & rfc7579"; 
		choice grid-type {
		    description "grid-type: DWDM, CWDM, etc.";
			case dwdm {
				leaf label-start {
				    type decimal64 {
						fraction-digits 5;
					}
					units THz; 
					description "the start label frequency, e.g, 192000";
				}
				leaf label-end {
				    type decimal64 {
						fraction-digits 5;
					}
					units THz; 
					description "the end label frequency, e.g, 196000"; 
				}
				leaf label-step {
					type channel-spacing-type; 
					description 
					"label-step is the channel-spacing (GHz), e.g., 
					100, 50, 25, or 12.5 GHz for DWDM";
					reference "RFC6205"; 
				}
				leaf priority {
					type uint8 {
						range "0..7";
					}
					description "TE LSP priority for setup";
					reference "RFC3209";
				}
			}
		    case cwdm {
				leaf label-start {
				    type uint32; 
					description "the start wavelengh for CWDM, e.g, 1520";
				}
				leaf label-end {
				    type uint32; 
					units THz; 
					description "the start wavelengh for CWDM, e.g, 1600";
				}
				leaf label-step {
					type string; 
					description 
					"label-step is the channel-spacing (nm), i.e.,
					20 nm for CWDM, which is the only value defined for CWDM";
					reference "RFC6205"; 
				}
				leaf priority {
					type uint8 {
						range "0..7";
					}
					description "TE LSP priority for setup";
					reference "RFC3209";
				}
	        }
		}
	}
	
    grouping wson-path-constraints {
      description
        "Global named path constraints configuration
         grouping for WSON tunnel";
         
      leaf wavelength-assignment {
        type identityref {
          base wson-types:wavelength-assignment;
        }
        description "Wavelength Allocation Method";
      }
    }

    augment "/te:te/te:tunnels/te:tunnel" {
        description
                "Augment with additional parameters required for WSON
                tunnel.";
        uses wson-tunnel-endpoint;
		uses wson-tunnel-resource; 
    }

    augment "/te:te/te:tunnels/te:tunnel/te:state" {
        description
                "Augment with additional parameters required for WSON
                tunnel.";
        uses wson-tunnel-endpoint;
		uses wson-tunnel-resource; 
    }

    augment "/te:te/te:globals/te:named-path-constraints/"
        + "te:named-path-constraint" {
        description
                "Augment with additional constraints WSON
                tunnel.";
        uses wson-path-constraints;
    }

    augment "/te:tunnels-rpc/te:input/te:tunnel-info/"
        + "tepc:path-request" {
        description 
				"Augment with additional constraints WSON
                tunnel.";
		uses wson-tunnel-endpoint;
        uses wson-path-constraints;
    }

    
}
